-- *****************************************************************
-- Cohesity Secondary Storage Appliance MIB
--
-- DO NOT EDIT THIS FILE MANUALLY. IT IS AUTOMATICALLY GENERATED BY
-- COHESITY MIB GENERATOR.
--
-- March, 2016 Roy Yang
--
-- Copyright (c) 2017 by Cohesity, Inc.
--
-- All rights reserved.
--
-- *****************************************************************
--
-- Top-level infrastructure of the Cohesity Appliance enterprise MIB tree.
--
COHESITY-APPLIANCE-MIB DEFINITIONS ::= BEGIN

-- *****************************************************************
--
-- IMPORTS section
--
-- *****************************************************************
IMPORTS
  PhysAddress, DisplayString, TEXTUAL-CONVENTION FROM SNMPv2-TC
  IANAifType FROM IANAifType-MIB
  MODULE-COMPLIANCE, OBJECT-GROUP, NOTIFICATION-GROUP FROM SNMPv2-CONF
  MODULE-IDENTITY, OBJECT-TYPE, NOTIFICATION-TYPE, enterprises, Integer32, Gauge32, Counter32, Counter64, TimeTicks, IpAddress, Opaque FROM SNMPv2-SMI
;

-- *****************************************************************
--
-- MODULE IDENTITY AND REVISION GROUP
--
-- *****************************************************************

cohesityApplianceMIB  MODULE-IDENTITY
  LAST-UPDATED "201804040126Z" -- UTC format is YYMMDDHHmmZ
  ORGANIZATION "Cohesity Inc."
  CONTACT-INFO "Roy Yang, roy@cohesity.com"
  DESCRIPTION
    "Cohesity OS enterprise-specific MIB tree."
    REVISION "201804040126Z"
    DESCRIPTION "Initial draft 0.2"
  ::= { enterprises 47421 }

-- *****************************************************************
--
-- OBJECT IDENTIFIER definition section
--
-- *****************************************************************

caNotifsGroup  OBJECT IDENTIFIER ::= { cohesityApplianceMIB 0 }

caEventVariables  OBJECT IDENTIFIER ::= { cohesityApplianceMIB 1 }

cohesityApplianceMIBConformance  OBJECT IDENTIFIER ::= { cohesityApplianceMIB 2 }

caSysInfoGroup  OBJECT IDENTIFIER ::= { cohesityApplianceMIB 3 }

caSysInfoClusterGroup  OBJECT IDENTIFIER ::= { caSysInfoGroup 100 }

caSysInfoChassisGroup  OBJECT IDENTIFIER ::= { caSysInfoGroup 200 }

caSysInfoPowerSupplyGroup  OBJECT IDENTIFIER ::= { caSysInfoGroup 300 }

caSysInfoFanGroup  OBJECT IDENTIFIER ::= { caSysInfoGroup 400 }

caSysInfoNodeGroup  OBJECT IDENTIFIER ::= { caSysInfoGroup 500 }

caSysInfoProcessorGroup  OBJECT IDENTIFIER ::= { caSysInfoGroup 600 }

caSysInfoMemoryGroup  OBJECT IDENTIFIER ::= { caSysInfoGroup 700 }

caSysInfoDiskGroup  OBJECT IDENTIFIER ::= { caSysInfoGroup 800 }

caSysInfoInterfaceGroup  OBJECT IDENTIFIER ::= { caSysInfoGroup 900 }

caSysInfoMiscGroup  OBJECT IDENTIFIER ::= { caSysInfoGroup 1000 }

caSysStatsGroup  OBJECT IDENTIFIER ::= { cohesityApplianceMIB 4 }

-- *****************************************************************
--
-- Cohesity Appliance enterprise-specific management objects group.
--
-- OBJECT Group definition section
--
-- *****************************************************************

clusterName OBJECT-TYPE
  SYNTAX DisplayString
  MAX-ACCESS read-only
  STATUS current
  DESCRIPTION
    "Cluster's Name."
  ::= { caSysInfoClusterGroup 1 }

clusterId OBJECT-TYPE
  SYNTAX DisplayString
  MAX-ACCESS read-only
  STATUS current
  DESCRIPTION
    "Cluster's ID."
  ::= { caSysInfoClusterGroup 2 }

clusterSoftwareVersion OBJECT-TYPE
  SYNTAX DisplayString
  MAX-ACCESS read-only
  STATUS current
  DESCRIPTION
    "Cluster's Software Version."
  ::= { caSysInfoClusterGroup 3 }

clusterNodeCount OBJECT-TYPE
  SYNTAX DisplayString
  MAX-ACCESS read-only
  STATUS current
  DESCRIPTION
    "Cluster's Node Count."
  ::= { caSysInfoClusterGroup 4 }

clusterState OBJECT-TYPE
  SYNTAX DisplayString
  MAX-ACCESS read-only
  STATUS current
  DESCRIPTION
    "Cluster's State."
  ::= { caSysInfoClusterGroup 5 }

clusterCreateTime OBJECT-TYPE
  SYNTAX DisplayString
  MAX-ACCESS read-only
  STATUS current
  DESCRIPTION
    "Cluster's CreateTime."
  ::= { caSysInfoClusterGroup 6 }

clusterCapacity OBJECT-TYPE
  SYNTAX DisplayString
  MAX-ACCESS read-only
  STATUS current
  DESCRIPTION
    "Cluster's Capacity."
  ::= { caSysInfoClusterGroup 7 }

clusterUsage OBJECT-TYPE
  SYNTAX DisplayString
  MAX-ACCESS read-only
  STATUS current
  DESCRIPTION
    "Cluster's Usage."
  ::= { caSysInfoClusterGroup 8 }

chassisProduct OBJECT-TYPE
  SYNTAX DisplayString
  MAX-ACCESS read-only
  STATUS current
  DESCRIPTION
    "Chassis's Product."
  ::= { caSysInfoChassisGroup 1 }

chassisVendor OBJECT-TYPE
  SYNTAX DisplayString
  MAX-ACCESS read-only
  STATUS current
  DESCRIPTION
    "Chassis's Vendor."
  ::= { caSysInfoChassisGroup 2 }

chassisSerial OBJECT-TYPE
  SYNTAX DisplayString
  MAX-ACCESS read-only
  STATUS current
  DESCRIPTION
    "Chassis's Serial."
  ::= { caSysInfoChassisGroup 3 }

nodeSlot OBJECT-TYPE
  SYNTAX DisplayString
  MAX-ACCESS read-only
  STATUS current
  DESCRIPTION
    "Node's Slot."
  ::= { caSysInfoNodeGroup 1 }

nodeModel OBJECT-TYPE
  SYNTAX DisplayString
  MAX-ACCESS read-only
  STATUS current
  DESCRIPTION
    "Node's Model."
  ::= { caSysInfoNodeGroup 2 }

nodeVendor OBJECT-TYPE
  SYNTAX DisplayString
  MAX-ACCESS read-only
  STATUS current
  DESCRIPTION
    "Node's Vendor."
  ::= { caSysInfoNodeGroup 3 }

nodeBios OBJECT-TYPE
  SYNTAX DisplayString
  MAX-ACCESS read-only
  STATUS current
  DESCRIPTION
    "Node's Bios."
  ::= { caSysInfoNodeGroup 4 }

nodeID OBJECT-TYPE
  SYNTAX DisplayString
  MAX-ACCESS read-only
  STATUS current
  DESCRIPTION
    "Node's ID."
  ::= { caSysInfoNodeGroup 5 }

nodeIp OBJECT-TYPE
  SYNTAX DisplayString
  MAX-ACCESS read-only
  STATUS current
  DESCRIPTION
    "Node's IP."
  ::= { caSysInfoNodeGroup 6 }

nodeSoftwareVersion OBJECT-TYPE
  SYNTAX DisplayString
  MAX-ACCESS read-only
  STATUS current
  DESCRIPTION
    "Node's Software Version."
  ::= { caSysInfoNodeGroup 7 }

nodeUptime OBJECT-TYPE
  SYNTAX DisplayString
  MAX-ACCESS read-only
  STATUS current
  DESCRIPTION
    "Node's Uptime."
  ::= { caSysInfoNodeGroup 8 }

miscInteger32 OBJECT-TYPE
  SYNTAX Integer32
  MAX-ACCESS read-only
  STATUS current
  DESCRIPTION
    "Testing integer."
  ::= { caSysInfoMiscGroup 1 }

miscOctetString OBJECT-TYPE
  SYNTAX DisplayString
  MAX-ACCESS read-only
  STATUS current
  DESCRIPTION
    "Testing Octet String."
  ::= { caSysInfoMiscGroup 2 }

miscNull OBJECT-TYPE
  SYNTAX DisplayString
  MAX-ACCESS read-only
  STATUS current
  DESCRIPTION
    "Testing Null."
  ::= { caSysInfoMiscGroup 3 }

miscObjectId OBJECT-TYPE
  SYNTAX DisplayString
  MAX-ACCESS read-only
  STATUS current
  DESCRIPTION
    "Testing Object Identifier."
  ::= { caSysInfoMiscGroup 4 }

miscCounter32 OBJECT-TYPE
  SYNTAX Counter32
  MAX-ACCESS read-only
  STATUS current
  DESCRIPTION
    "Testing Counter32r."
  ::= { caSysInfoMiscGroup 5 }

miscIPAddress OBJECT-TYPE
  SYNTAX IpAddress
  MAX-ACCESS read-only
  STATUS current
  DESCRIPTION
    "Testing IP Address."
  ::= { caSysInfoMiscGroup 6 }

miscGauge32 OBJECT-TYPE
  SYNTAX Gauge32
  MAX-ACCESS read-only
  STATUS current
  DESCRIPTION
    "Testing Gauge32."
  ::= { caSysInfoMiscGroup 7 }

miscTimeTicks OBJECT-TYPE
  SYNTAX TimeTicks
  MAX-ACCESS read-only
  STATUS current
  DESCRIPTION
    "Testing TimeTicks."
  ::= { caSysInfoMiscGroup 8 }

miscOpaque OBJECT-TYPE
  SYNTAX Opaque
  MAX-ACCESS read-only
  STATUS current
  DESCRIPTION
    "Testing Opaque."
  ::= { caSysInfoMiscGroup 9 }

miscCounter64 OBJECT-TYPE
  SYNTAX Counter64
  MAX-ACCESS read-only
  STATUS current
  DESCRIPTION
    "Testing Counter64."
  ::= { caSysInfoMiscGroup 10 }

-- *****************************************************************
--
-- Cohesity Appliance enterprise-specific management objects.
--
-- OBJECT TABLE definition section
--
-- *****************************************************************

powerSupplyInfoTable OBJECT-TYPE    -- the table object
  SYNTAX SEQUENCE OF PowerSupplyInfoEntry
  MAX-ACCESS not-accessible
  STATUS current
  DESCRIPTION
    "Power supply information table."
  ::= { caSysInfoPowerSupplyGroup 1 }

powerSupplyInfoEntry OBJECT-TYPE    -- the entry object
  SYNTAX PowerSupplyInfoEntry
  MAX-ACCESS not-accessible
  STATUS current
  DESCRIPTION
    "Power supply information table."
  INDEX { psSlot }
  ::= { powerSupplyInfoTable 1 }

PowerSupplyInfoEntry ::=          -- the SEQUENCE statement
  SEQUENCE {
    psSlot    DisplayString,
    psWatts    DisplayString,
    psState    DisplayString
}

psSlot OBJECT-TYPE
  SYNTAX DisplayString
  MAX-ACCESS read-only
  STATUS current
  DESCRIPTION
    "Power supply slot."
  ::= { powerSupplyInfoEntry 1 }

psWatts OBJECT-TYPE
  SYNTAX DisplayString
  MAX-ACCESS read-only
  STATUS current
  DESCRIPTION
    "Power supply Output Watts."
  ::= { powerSupplyInfoEntry 2 }

psState OBJECT-TYPE
  SYNTAX DisplayString
  MAX-ACCESS read-only
  STATUS current
  DESCRIPTION
    "Power supply state."
  ::= { powerSupplyInfoEntry 3 }

fanInfoTable OBJECT-TYPE    -- the table object
  SYNTAX SEQUENCE OF FanInfoEntry
  MAX-ACCESS not-accessible
  STATUS current
  DESCRIPTION
    "Fan information table."
  ::= { caSysInfoFanGroup 1 }

fanInfoEntry OBJECT-TYPE    -- the entry object
  SYNTAX FanInfoEntry
  MAX-ACCESS not-accessible
  STATUS current
  DESCRIPTION
    "Fan information table."
  INDEX { fanSlot }
  ::= { fanInfoTable 1 }

FanInfoEntry ::=          -- the SEQUENCE statement
  SEQUENCE {
    fanSlot    DisplayString,
    fanRpm    DisplayString,
    fanState    DisplayString
}

fanSlot OBJECT-TYPE
  SYNTAX DisplayString
  MAX-ACCESS read-only
  STATUS current
  DESCRIPTION
    "FAN slot."
  ::= { fanInfoEntry 1 }

fanRpm OBJECT-TYPE
  SYNTAX DisplayString
  MAX-ACCESS read-only
  STATUS current
  DESCRIPTION
    "FAN RPm."
  ::= { fanInfoEntry 2 }

fanState OBJECT-TYPE
  SYNTAX DisplayString
  MAX-ACCESS read-only
  STATUS current
  DESCRIPTION
    "FAN state."
  ::= { fanInfoEntry 3 }

memInfoTable OBJECT-TYPE    -- the table object
  SYNTAX SEQUENCE OF MemInfoEntry
  MAX-ACCESS not-accessible
  STATUS current
  DESCRIPTION
    "DIMM's information table."
  ::= { caSysInfoMemoryGroup 1 }

memInfoEntry OBJECT-TYPE    -- the entry object
  SYNTAX MemInfoEntry
  MAX-ACCESS not-accessible
  STATUS current
  DESCRIPTION
    "DIMM's information table."
  INDEX { memSlot }
  ::= { memInfoTable 1 }

MemInfoEntry ::=          -- the SEQUENCE statement
  SEQUENCE {
    memSlot    DisplayString,
    memVendor    DisplayString,
    memSize    DisplayString,
    memSpeed    DisplayString,
    memState    DisplayString
}

memSlot OBJECT-TYPE
  SYNTAX DisplayString
  MAX-ACCESS read-only
  STATUS current
  DESCRIPTION
    "DIMM's Slot."
  ::= { memInfoEntry 1 }

memVendor OBJECT-TYPE
  SYNTAX DisplayString
  MAX-ACCESS read-only
  STATUS current
  DESCRIPTION
    "DIMM's Vendor."
  ::= { memInfoEntry 2 }

memSize OBJECT-TYPE
  SYNTAX DisplayString
  MAX-ACCESS read-only
  STATUS current
  DESCRIPTION
    "DIMM's Size."
  ::= { memInfoEntry 3 }

memSpeed OBJECT-TYPE
  SYNTAX DisplayString
  MAX-ACCESS read-only
  STATUS current
  DESCRIPTION
    "DIMM's Speed."
  ::= { memInfoEntry 4 }

memState OBJECT-TYPE
  SYNTAX DisplayString
  MAX-ACCESS read-only
  STATUS current
  DESCRIPTION
    "DIMM's State."
  ::= { memInfoEntry 5 }

cpuInfoTable OBJECT-TYPE    -- the table object
  SYNTAX SEQUENCE OF CpuInfoEntry
  MAX-ACCESS not-accessible
  STATUS current
  DESCRIPTION
    "Processor's information table."
  ::= { caSysInfoProcessorGroup 1 }

cpuInfoEntry OBJECT-TYPE    -- the entry object
  SYNTAX CpuInfoEntry
  MAX-ACCESS not-accessible
  STATUS current
  DESCRIPTION
    "Processor's information table."
  INDEX { cpuSlot }
  ::= { cpuInfoTable 1 }

CpuInfoEntry ::=          -- the SEQUENCE statement
  SEQUENCE {
    cpuSlot    DisplayString,
    cpuVendor    DisplayString,
    cpuVersion    DisplayString,
    cpuSpeed    DisplayString,
    cpuCoreCount    DisplayString,
    cpudState    DisplayString
}

cpuSlot OBJECT-TYPE
  SYNTAX DisplayString
  MAX-ACCESS read-only
  STATUS current
  DESCRIPTION
    "CPU's Slot."
  ::= { cpuInfoEntry 1 }

cpuVendor OBJECT-TYPE
  SYNTAX DisplayString
  MAX-ACCESS read-only
  STATUS current
  DESCRIPTION
    "CPU's Vendor."
  ::= { cpuInfoEntry 2 }

cpuVersion OBJECT-TYPE
  SYNTAX DisplayString
  MAX-ACCESS read-only
  STATUS current
  DESCRIPTION
    "CPU's Version."
  ::= { cpuInfoEntry 3 }

cpuSpeed OBJECT-TYPE
  SYNTAX DisplayString
  MAX-ACCESS read-only
  STATUS current
  DESCRIPTION
    "Cpu's Speed."
  ::= { cpuInfoEntry 4 }

cpuCoreCount OBJECT-TYPE
  SYNTAX DisplayString
  MAX-ACCESS read-only
  STATUS current
  DESCRIPTION
    "Cpu's Core Count."
  ::= { cpuInfoEntry 5 }

cpudState OBJECT-TYPE
  SYNTAX DisplayString
  MAX-ACCESS read-only
  STATUS current
  DESCRIPTION
    "CPU's State."
  ::= { cpuInfoEntry 6 }

diskInfoTable OBJECT-TYPE    -- the table object
  SYNTAX SEQUENCE OF DiskInfoEntry
  MAX-ACCESS not-accessible
  STATUS current
  DESCRIPTION
    "Disk information table."
  ::= { caSysInfoDiskGroup 1 }

diskInfoEntry OBJECT-TYPE    -- the entry object
  SYNTAX DiskInfoEntry
  MAX-ACCESS not-accessible
  STATUS current
  DESCRIPTION
    "Disk information table."
  INDEX { diskSlot }
  ::= { diskInfoTable 1 }

DiskInfoEntry ::=          -- the SEQUENCE statement
  SEQUENCE {
    diskSlot    DisplayString,
    diskVendor    DisplayString,
    diskModel    DisplayString,
    diskSerial    DisplayString,
    diskFirmware    DisplayString,
    diskCapacity    DisplayString,
    diskUsage    DisplayString,
    diskState    DisplayString
}

diskSlot OBJECT-TYPE
  SYNTAX DisplayString
  MAX-ACCESS read-only
  STATUS current
  DESCRIPTION
    "Disk slot."
  ::= { diskInfoEntry 1 }

diskVendor OBJECT-TYPE
  SYNTAX DisplayString
  MAX-ACCESS read-only
  STATUS current
  DESCRIPTION
    "Disk Vendor."
  ::= { diskInfoEntry 2 }

diskModel OBJECT-TYPE
  SYNTAX DisplayString
  MAX-ACCESS read-only
  STATUS current
  DESCRIPTION
    "Disk's Model."
  ::= { diskInfoEntry 3 }

diskSerial OBJECT-TYPE
  SYNTAX DisplayString
  MAX-ACCESS read-only
  STATUS current
  DESCRIPTION
    "Disk's Serial."
  ::= { diskInfoEntry 4 }

diskFirmware OBJECT-TYPE
  SYNTAX DisplayString
  MAX-ACCESS read-only
  STATUS current
  DESCRIPTION
    "Disk's Firmware."
  ::= { diskInfoEntry 5 }

diskCapacity OBJECT-TYPE
  SYNTAX DisplayString
  MAX-ACCESS read-only
  STATUS current
  DESCRIPTION
    "Disk's Capacity."
  ::= { diskInfoEntry 6 }

diskUsage OBJECT-TYPE
  SYNTAX DisplayString
  MAX-ACCESS read-only
  STATUS current
  DESCRIPTION
    "Disk's Usage."
  ::= { diskInfoEntry 7 }

diskState OBJECT-TYPE
  SYNTAX DisplayString
  MAX-ACCESS read-only
  STATUS current
  DESCRIPTION
    "Disk's State."
  ::= { diskInfoEntry 8 }

ifInfoTable OBJECT-TYPE    -- the table object
  SYNTAX SEQUENCE OF IfInfoEntry
  MAX-ACCESS not-accessible
  STATUS current
  DESCRIPTION
    "Interface information table."
  ::= { caSysInfoInterfaceGroup 1 }

ifInfoEntry OBJECT-TYPE    -- the entry object
  SYNTAX IfInfoEntry
  MAX-ACCESS not-accessible
  STATUS current
  DESCRIPTION
    "Interface information table."
  INDEX { ifIndex }
  ::= { ifInfoTable 1 }

IfInfoEntry ::=          -- the SEQUENCE statement
  SEQUENCE {
    ifIndex    Counter32,
    ifDescr    DisplayString,
    ifType    IANAifType,
    ifMtu    Integer32,
    ifSpeed    Gauge32,
    ifPhysAddress    PhysAddress,
    ifAdminStatus    INTEGER,
    ifLastChange    TimeTicks,
    ifInOctets    Counter32,
    ifInErrors    Counter32,
    ifOutOctets    Counter32,
    ifOutErrors    Counter32,
    ifState    DisplayString
}

ifIndex OBJECT-TYPE
  SYNTAX Counter32
  MAX-ACCESS read-only
  STATUS current
  DESCRIPTION
    "Interface Index."
  ::= { ifInfoEntry 1 }

ifDescr OBJECT-TYPE
  SYNTAX DisplayString
  MAX-ACCESS read-only
  STATUS current
  DESCRIPTION
    "Interface Description."
  ::= { ifInfoEntry 2 }

ifType OBJECT-TYPE
  SYNTAX IANAifType
  MAX-ACCESS read-only
  STATUS current
  DESCRIPTION
    "Interface Type."
  ::= { ifInfoEntry 3 }

ifMtu OBJECT-TYPE
  SYNTAX Integer32
  MAX-ACCESS read-only
  STATUS current
  DESCRIPTION
    "Interface's MTU."
  ::= { ifInfoEntry 4 }

ifSpeed OBJECT-TYPE
  SYNTAX Gauge32
  MAX-ACCESS read-only
  STATUS current
  DESCRIPTION
    "Interface's Speed."
  ::= { ifInfoEntry 5 }

ifPhysAddress OBJECT-TYPE
  SYNTAX PhysAddress
  MAX-ACCESS read-only
  STATUS current
  DESCRIPTION
    "Interface Physical address."
  ::= { ifInfoEntry 6 }

ifAdminStatus OBJECT-TYPE
  SYNTAX INTEGER
  MAX-ACCESS read-only
  STATUS current
  DESCRIPTION
    "Interface's admin status."
  ::= { ifInfoEntry 7 }

ifLastChange OBJECT-TYPE
  SYNTAX TimeTicks
  MAX-ACCESS read-only
  STATUS current
  DESCRIPTION
    "Interface's last change."
  ::= { ifInfoEntry 8 }

ifInOctets OBJECT-TYPE
  SYNTAX Counter32
  MAX-ACCESS read-only
  STATUS current
  DESCRIPTION
    "Interface's incoming packets."
  ::= { ifInfoEntry 9 }

ifInErrors OBJECT-TYPE
  SYNTAX Counter32
  MAX-ACCESS read-only
  STATUS current
  DESCRIPTION
    "Interface's incoming packets errors."
  ::= { ifInfoEntry 10 }

ifOutOctets OBJECT-TYPE
  SYNTAX Counter32
  MAX-ACCESS read-only
  STATUS current
  DESCRIPTION
    "Interface's sending packets."
  ::= { ifInfoEntry 11 }

ifOutErrors OBJECT-TYPE
  SYNTAX Counter32
  MAX-ACCESS read-only
  STATUS current
  DESCRIPTION
    "Interface's sending packets errors."
  ::= { ifInfoEntry 12 }

ifState OBJECT-TYPE
  SYNTAX DisplayString
  MAX-ACCESS read-only
  STATUS current
  DESCRIPTION
    "Interface's state."
  ::= { ifInfoEntry 13 }

-- *****************************************************************
--
-- Cohesity Appliance enterprise-specific management objects.
--
-- OBJECT TYPE definition section
--
-- *****************************************************************

diskNotHealthyEvent OBJECT-TYPE
  SYNTAX DisplayString
  MAX-ACCESS read-only
  STATUS current
  DESCRIPTION
    "Disk is not healthy."
  ::= { caEventVariables 1 }

nodeIsDownEvent OBJECT-TYPE
  SYNTAX DisplayString
  MAX-ACCESS read-only
  STATUS current
  DESCRIPTION
    "Node becomes bad."
  ::= { caEventVariables 2 }

diskOfflineEvent OBJECT-TYPE
  SYNTAX DisplayString
  MAX-ACCESS read-only
  STATUS current
  DESCRIPTION
    "Disk is offline."
  ::= { caEventVariables 3 }

upgradeFailedEvent OBJECT-TYPE
  SYNTAX DisplayString
  MAX-ACCESS read-only
  STATUS current
  DESCRIPTION
    "Node failed to upgrade."
  ::= { caEventVariables 4 }

newDiskFoundEvent OBJECT-TYPE
  SYNTAX DisplayString
  MAX-ACCESS read-only
  STATUS current
  DESCRIPTION
    "New disk is found."
  ::= { caEventVariables 5 }

logsDiskSpaceLowEvent OBJECT-TYPE
  SYNTAX DisplayString
  MAX-ACCESS read-only
  STATUS current
  DESCRIPTION
    "Logs partition disk space is low."
  ::= { caEventVariables 6 }

timeServiceEvent OBJECT-TYPE
  SYNTAX DisplayString
  MAX-ACCESS read-only
  STATUS current
  DESCRIPTION
    "Node can not sync time."
  ::= { caEventVariables 7 }

missingDiskEvent OBJECT-TYPE
  SYNTAX DisplayString
  MAX-ACCESS read-only
  STATUS current
  DESCRIPTION
    "One or more disks are missing."
  ::= { caEventVariables 8 }

writeLimitEvent OBJECT-TYPE
  SYNTAX DisplayString
  MAX-ACCESS read-only
  STATUS current
  DESCRIPTION
    "SSD is reaching its write limit."
  ::= { caEventVariables 9 }

memUncorrectableEccEvent OBJECT-TYPE
  SYNTAX DisplayString
  MAX-ACCESS read-only
  STATUS current
  DESCRIPTION
    "Memory found uncorrectable ECC."
  ::= { caEventVariables 10 }

memCorrectableEccEvent OBJECT-TYPE
  SYNTAX DisplayString
  MAX-ACCESS read-only
  STATUS current
  DESCRIPTION
    "Memory found Correctable ECC."
  ::= { caEventVariables 11 }

watchdogTriggeredEvent OBJECT-TYPE
  SYNTAX DisplayString
  MAX-ACCESS read-only
  STATUS current
  DESCRIPTION
    "IPMI watchdog triggered."
  ::= { caEventVariables 12 }

tempOutOfHighRangeEvent OBJECT-TYPE
  SYNTAX DisplayString
  MAX-ACCESS read-only
  STATUS current
  DESCRIPTION
    "Temperature Sensor Out of High Range."
  ::= { caEventVariables 13 }

tempOutOfLowRangeEvent OBJECT-TYPE
  SYNTAX DisplayString
  MAX-ACCESS read-only
  STATUS current
  DESCRIPTION
    "Temperature Sensor Out of Low Range."
  ::= { caEventVariables 14 }

voltOutOfHighRangeEvent OBJECT-TYPE
  SYNTAX DisplayString
  MAX-ACCESS read-only
  STATUS current
  DESCRIPTION
    "Voltage Sensor Out of High Range."
  ::= { caEventVariables 15 }

voltOutOfLowRangeEvent OBJECT-TYPE
  SYNTAX DisplayString
  MAX-ACCESS read-only
  STATUS current
  DESCRIPTION
    "Voltage Sensor Out of Low Range."
  ::= { caEventVariables 16 }

hddDriveRemovedEvent OBJECT-TYPE
  SYNTAX DisplayString
  MAX-ACCESS read-only
  STATUS current
  DESCRIPTION
    "HDD drive is removed."
  ::= { caEventVariables 17 }

hddDrivePresentEvent OBJECT-TYPE
  SYNTAX DisplayString
  MAX-ACCESS read-only
  STATUS current
  DESCRIPTION
    "HDD drive is present."
  ::= { caEventVariables 18 }

hddDriveFaultEvent OBJECT-TYPE
  SYNTAX DisplayString
  MAX-ACCESS read-only
  STATUS current
  DESCRIPTION
    "HDD drive is faulty."
  ::= { caEventVariables 19 }

powerSupplyRemovedEvent OBJECT-TYPE
  SYNTAX DisplayString
  MAX-ACCESS read-only
  STATUS current
  DESCRIPTION
    "Power supply is removed."
  ::= { caEventVariables 20 }

powerSupplyInsertedEvent OBJECT-TYPE
  SYNTAX DisplayString
  MAX-ACCESS read-only
  STATUS current
  DESCRIPTION
    "Power supply is inserted."
  ::= { caEventVariables 21 }

linkIsDownEvent OBJECT-TYPE
  SYNTAX DisplayString
  MAX-ACCESS read-only
  STATUS current
  DESCRIPTION
    "Interface is down."
  ::= { caEventVariables 22 }

linkIsUpEvent OBJECT-TYPE
  SYNTAX DisplayString
  MAX-ACCESS read-only
  STATUS current
  DESCRIPTION
    "Interface is up."
  ::= { caEventVariables 23 }

ipmiSelClearedEvent OBJECT-TYPE
  SYNTAX DisplayString
  MAX-ACCESS read-only
  STATUS current
  DESCRIPTION
    "IPMI SEL log cleared."
  ::= { caEventVariables 24 }

nodeRebootedEvent OBJECT-TYPE
  SYNTAX DisplayString
  MAX-ACCESS read-only
  STATUS current
  DESCRIPTION
    "Node rebooted."
  ::= { caEventVariables 25 }

thermalTripTriggeredEvent OBJECT-TYPE
  SYNTAX DisplayString
  MAX-ACCESS read-only
  STATUS current
  DESCRIPTION
    "Thermal Trip Triggered."
  ::= { caEventVariables 26 }

powerSupplyAcLostEvent OBJECT-TYPE
  SYNTAX DisplayString
  MAX-ACCESS read-only
  STATUS current
  DESCRIPTION
    "Power supply AC lost."
  ::= { caEventVariables 27 }

nodeChassisChangedEvent OBJECT-TYPE
  SYNTAX DisplayString
  MAX-ACCESS read-only
  STATUS current
  DESCRIPTION
    "Chassis is changed."
  ::= { caEventVariables 28 }

raidDegradedEvent OBJECT-TYPE
  SYNTAX DisplayString
  MAX-ACCESS read-only
  STATUS current
  DESCRIPTION
    "RAID is degraded."
  ::= { caEventVariables 29 }

diskOnlineEvent OBJECT-TYPE
  SYNTAX DisplayString
  MAX-ACCESS read-only
  STATUS current
  DESCRIPTION
    "Disk is back online."
  ::= { caEventVariables 30 }

systemLedAmberEvent OBJECT-TYPE
  SYNTAX DisplayString
  MAX-ACCESS read-only
  STATUS current
  DESCRIPTION
    "System amber LED is on."
  ::= { caEventVariables 31 }

cpuThrottledEvent OBJECT-TYPE
  SYNTAX DisplayString
  MAX-ACCESS read-only
  STATUS current
  DESCRIPTION
    "CPU is throttled."
  ::= { caEventVariables 32 }

clusterHealthEvent OBJECT-TYPE
  SYNTAX DisplayString
  MAX-ACCESS read-only
  STATUS current
  DESCRIPTION
    "Internal error detected for cluster."
  ::= { caEventVariables 100 }

diskMarkedOfflineEvent OBJECT-TYPE
  SYNTAX DisplayString
  MAX-ACCESS read-only
  STATUS current
  DESCRIPTION
    "Disk is marked offline."
  ::= { caEventVariables 101 }

activeDirectoryNotReachableEvent OBJECT-TYPE
  SYNTAX DisplayString
  MAX-ACCESS read-only
  STATUS current
  DESCRIPTION
    "Active directory is not reachable."
  ::= { caEventVariables 102 }

kernelPanicEvent OBJECT-TYPE
  SYNTAX DisplayString
  MAX-ACCESS read-only
  STATUS current
  DESCRIPTION
    "Node crashed from a kernel panic."
  ::= { caEventVariables 103 }

clusterSpaceUsageHighEvent OBJECT-TYPE
  SYNTAX DisplayString
  MAX-ACCESS read-only
  STATUS current
  DESCRIPTION
    "Cluster space usage is high."
  ::= { caEventVariables 104 }

viewBoxSpaceUsageHighEvent OBJECT-TYPE
  SYNTAX DisplayString
  MAX-ACCESS read-only
  STATUS current
  DESCRIPTION
    "Viewbox space usage is high."
  ::= { caEventVariables 105 }

nodeFailureIsNotToleratedEvent OBJECT-TYPE
  SYNTAX DisplayString
  MAX-ACCESS read-only
  STATUS current
  DESCRIPTION
    "Cluster is not able to tolerate node failure."
  ::= { caEventVariables 106 }

searchClusterHealthEvent OBJECT-TYPE
  SYNTAX DisplayString
  MAX-ACCESS read-only
  STATUS current
  DESCRIPTION
    "Search cluster is not healthy."
  ::= { caEventVariables 107 }

backupJobFailedEvent OBJECT-TYPE
  SYNTAX DisplayString
  MAX-ACCESS read-only
  STATUS current
  DESCRIPTION
    "Backup run of job failed."
  ::= { caEventVariables 108 }

backupObjectFailedEvent OBJECT-TYPE
  SYNTAX DisplayString
  MAX-ACCESS read-only
  STATUS current
  DESCRIPTION
    "Backup run of object failed."
  ::= { caEventVariables 109 }

metadataServerUnreachableEvent OBJECT-TYPE
  SYNTAX DisplayString
  MAX-ACCESS read-only
  STATUS current
  DESCRIPTION
    "Metadata server unreachable for long time."
  ::= { caEventVariables 110 }

metadataUnavailableEvent OBJECT-TYPE
  SYNTAX DisplayString
  MAX-ACCESS read-only
  STATUS current
  DESCRIPTION
    "Metadata is unavailable due to multiple failures."
  ::= { caEventVariables 111 }

metadataShuffleNotProgressingEvent OBJECT-TYPE
  SYNTAX DisplayString
  MAX-ACCESS read-only
  STATUS current
  DESCRIPTION
    "Metadata shuffle not progressing due to load constraint."
  ::= { caEventVariables 112 }

cohesitySnmpTestEvent OBJECT-TYPE
  SYNTAX DisplayString
  MAX-ACCESS read-only
  STATUS current
  DESCRIPTION
    "Cohesity SNMP Test Notification."
  ::= { caEventVariables 10000 }

-- *****************************************************************
--
-- NOTIFICATION TYPE definition section
--
-- *****************************************************************

diskNotHealthyNotif NOTIFICATION-TYPE
  OBJECTS { diskNotHealthyEvent }
  STATUS current
  DESCRIPTION
    "Disk is not healthy."
  ::= { caNotifsGroup 1 }

nodeIsDownNotif NOTIFICATION-TYPE
  OBJECTS { nodeIsDownEvent }
  STATUS current
  DESCRIPTION
    "Node becomes bad."
  ::= { caNotifsGroup 2 }

diskOfflineNotif NOTIFICATION-TYPE
  OBJECTS { diskOfflineEvent }
  STATUS current
  DESCRIPTION
    "Disk is offline."
  ::= { caNotifsGroup 3 }

upgradeFailedNotif NOTIFICATION-TYPE
  OBJECTS { upgradeFailedEvent }
  STATUS current
  DESCRIPTION
    "Node failed to upgrade."
  ::= { caNotifsGroup 4 }

newDiskFoundNotif NOTIFICATION-TYPE
  OBJECTS { newDiskFoundEvent }
  STATUS current
  DESCRIPTION
    "New disk is found."
  ::= { caNotifsGroup 5 }

logsDiskSpaceLowNotif NOTIFICATION-TYPE
  OBJECTS { logsDiskSpaceLowEvent }
  STATUS current
  DESCRIPTION
    "Logs partition disk space is low."
  ::= { caNotifsGroup 6 }

timeServiceNotif NOTIFICATION-TYPE
  OBJECTS { timeServiceEvent }
  STATUS current
  DESCRIPTION
    "Node can not sync time."
  ::= { caNotifsGroup 7 }

missingDiskNotif NOTIFICATION-TYPE
  OBJECTS { missingDiskEvent }
  STATUS current
  DESCRIPTION
    "One or more disks are missing."
  ::= { caNotifsGroup 8 }

writeLimitNotif NOTIFICATION-TYPE
  OBJECTS { writeLimitEvent }
  STATUS current
  DESCRIPTION
    "SSD is reaching its write limit."
  ::= { caNotifsGroup 9 }

memUncorrectableEccNotif NOTIFICATION-TYPE
  OBJECTS { memUncorrectableEccEvent }
  STATUS current
  DESCRIPTION
    "Memory found uncorrectable ECC."
  ::= { caNotifsGroup 10 }

memCorrectableEccNotif NOTIFICATION-TYPE
  OBJECTS { memCorrectableEccEvent }
  STATUS current
  DESCRIPTION
    "Memory found Correctable ECC."
  ::= { caNotifsGroup 11 }

watchdogTriggeredNotif NOTIFICATION-TYPE
  OBJECTS { watchdogTriggeredEvent }
  STATUS current
  DESCRIPTION
    "IPMI watchdog triggered."
  ::= { caNotifsGroup 12 }

tempOutOfHighRangeNotif NOTIFICATION-TYPE
  OBJECTS { tempOutOfHighRangeEvent }
  STATUS current
  DESCRIPTION
    "Temperature Sensor Out of High Range."
  ::= { caNotifsGroup 13 }

tempOutOfLowRangeNotif NOTIFICATION-TYPE
  OBJECTS { tempOutOfLowRangeEvent }
  STATUS current
  DESCRIPTION
    "Temperature Sensor Out of Low Range."
  ::= { caNotifsGroup 14 }

voltOutOfHighRangeNotif NOTIFICATION-TYPE
  OBJECTS { voltOutOfHighRangeEvent }
  STATUS current
  DESCRIPTION
    "Voltage Sensor Out of High Range."
  ::= { caNotifsGroup 15 }

voltOutOfLowRangeNotif NOTIFICATION-TYPE
  OBJECTS { voltOutOfLowRangeEvent }
  STATUS current
  DESCRIPTION
    "Voltage Sensor Out of Low Range."
  ::= { caNotifsGroup 16 }

hddDriveRemovedNotif NOTIFICATION-TYPE
  OBJECTS { hddDriveRemovedEvent }
  STATUS current
  DESCRIPTION
    "HDD drive is removed."
  ::= { caNotifsGroup 17 }

hddDrivePresentNotif NOTIFICATION-TYPE
  OBJECTS { hddDrivePresentEvent }
  STATUS current
  DESCRIPTION
    "HDD drive is present."
  ::= { caNotifsGroup 18 }

hddDriveFaultNotif NOTIFICATION-TYPE
  OBJECTS { hddDriveFaultEvent }
  STATUS current
  DESCRIPTION
    "HDD drive is faulty."
  ::= { caNotifsGroup 19 }

powerSupplyRemovedNotif NOTIFICATION-TYPE
  OBJECTS { powerSupplyRemovedEvent }
  STATUS current
  DESCRIPTION
    "Power supply is removed."
  ::= { caNotifsGroup 20 }

powerSupplyInsertedNotif NOTIFICATION-TYPE
  OBJECTS { powerSupplyInsertedEvent }
  STATUS current
  DESCRIPTION
    "Power supply is inserted."
  ::= { caNotifsGroup 21 }

linkIsDownNotif NOTIFICATION-TYPE
  OBJECTS { linkIsDownEvent }
  STATUS current
  DESCRIPTION
    "Interface is down."
  ::= { caNotifsGroup 22 }

linkIsUpNotif NOTIFICATION-TYPE
  OBJECTS { linkIsUpEvent }
  STATUS current
  DESCRIPTION
    "Interface is up."
  ::= { caNotifsGroup 23 }

ipmiSelClearedNotif NOTIFICATION-TYPE
  OBJECTS { ipmiSelClearedEvent }
  STATUS current
  DESCRIPTION
    "IPMI SEL log cleared."
  ::= { caNotifsGroup 24 }

nodeRebootedNotif NOTIFICATION-TYPE
  OBJECTS { nodeRebootedEvent }
  STATUS current
  DESCRIPTION
    "Node rebooted."
  ::= { caNotifsGroup 25 }

thermalTripTriggeredNotif NOTIFICATION-TYPE
  OBJECTS { thermalTripTriggeredEvent }
  STATUS current
  DESCRIPTION
    "Thermal Trip Triggered."
  ::= { caNotifsGroup 26 }

powerSupplyAcLostNotif NOTIFICATION-TYPE
  OBJECTS { powerSupplyAcLostEvent }
  STATUS current
  DESCRIPTION
    "Power supply AC lost."
  ::= { caNotifsGroup 27 }

nodeChassisChangedNotif NOTIFICATION-TYPE
  OBJECTS { nodeChassisChangedEvent }
  STATUS current
  DESCRIPTION
    "Chassis is changed."
  ::= { caNotifsGroup 28 }

raidDegradedNotif NOTIFICATION-TYPE
  OBJECTS { raidDegradedEvent }
  STATUS current
  DESCRIPTION
    "RAID is degraded."
  ::= { caNotifsGroup 29 }

diskOnlineNotif NOTIFICATION-TYPE
  OBJECTS { diskOnlineEvent }
  STATUS current
  DESCRIPTION
    "Disk is back online."
  ::= { caNotifsGroup 30 }

systemLedAmberNotif NOTIFICATION-TYPE
  OBJECTS { systemLedAmberEvent }
  STATUS current
  DESCRIPTION
    "System amber LED is on."
  ::= { caNotifsGroup 31 }

cpuThrottledNotif NOTIFICATION-TYPE
  OBJECTS { cpuThrottledEvent }
  STATUS current
  DESCRIPTION
    "CPU is throttled."
  ::= { caNotifsGroup 32 }

clusterHealthNotif NOTIFICATION-TYPE
  OBJECTS { clusterHealthEvent }
  STATUS current
  DESCRIPTION
    "Internal error detected for cluster."
  ::= { caNotifsGroup 100 }

diskMarkedOfflineNotif NOTIFICATION-TYPE
  OBJECTS { diskMarkedOfflineEvent }
  STATUS current
  DESCRIPTION
    "Disk is marked offline."
  ::= { caNotifsGroup 101 }

activeDirectoryNotReachableNotif NOTIFICATION-TYPE
  OBJECTS { activeDirectoryNotReachableEvent }
  STATUS current
  DESCRIPTION
    "Active directory is not reachable."
  ::= { caNotifsGroup 102 }

kernelPanicNotif NOTIFICATION-TYPE
  OBJECTS { kernelPanicEvent }
  STATUS current
  DESCRIPTION
    "Node crashed from a kernel panic."
  ::= { caNotifsGroup 103 }

clusterSpaceUsageHighNotif NOTIFICATION-TYPE
  OBJECTS { clusterSpaceUsageHighEvent }
  STATUS current
  DESCRIPTION
    "Cluster space usage is high."
  ::= { caNotifsGroup 104 }

viewBoxSpaceUsageHighNotif NOTIFICATION-TYPE
  OBJECTS { viewBoxSpaceUsageHighEvent }
  STATUS current
  DESCRIPTION
    "Viewbox space usage is high."
  ::= { caNotifsGroup 105 }

nodeFailureIsNotToleratedNotif NOTIFICATION-TYPE
  OBJECTS { nodeFailureIsNotToleratedEvent }
  STATUS current
  DESCRIPTION
    "Cluster is not able to tolerate node failure."
  ::= { caNotifsGroup 106 }

searchClusterHealthNotif NOTIFICATION-TYPE
  OBJECTS { searchClusterHealthEvent }
  STATUS current
  DESCRIPTION
    "Search cluster is not healthy."
  ::= { caNotifsGroup 107 }

backupJobFailedNotif NOTIFICATION-TYPE
  OBJECTS { backupJobFailedEvent }
  STATUS current
  DESCRIPTION
    "Backup run of job failed."
  ::= { caNotifsGroup 108 }

backupObjectFailedNotif NOTIFICATION-TYPE
  OBJECTS { backupObjectFailedEvent }
  STATUS current
  DESCRIPTION
    "Backup run of object failed."
  ::= { caNotifsGroup 109 }

metadataServerUnreachableNotif NOTIFICATION-TYPE
  OBJECTS { metadataServerUnreachableEvent }
  STATUS current
  DESCRIPTION
    "Metadata server unreachable for long time."
  ::= { caNotifsGroup 110 }

metadataUnavailableNotif NOTIFICATION-TYPE
  OBJECTS { metadataUnavailableEvent }
  STATUS current
  DESCRIPTION
    "Metadata is unavailable due to multiple failures."
  ::= { caNotifsGroup 111 }

metadataShuffleNotProgressingNotif NOTIFICATION-TYPE
  OBJECTS { metadataShuffleNotProgressingEvent }
  STATUS current
  DESCRIPTION
    "Metadata shuffle not progressing due to load constraint."
  ::= { caNotifsGroup 112 }

cohesitySnmpTestNotif NOTIFICATION-TYPE
  OBJECTS { cohesitySnmpTestEvent }
  STATUS current
  DESCRIPTION
    "Cohesity SNMP Test Notification."
  ::= { caNotifsGroup 10000 }

-- *****************************************************************
--
-- Conformance information section
--
-- *****************************************************************

cohesityApplianceMIBCompliances  OBJECT IDENTIFIER ::= { cohesityApplianceMIBConformance 1 }

cohesityApplianceMIBGroups  OBJECT IDENTIFIER ::= { cohesityApplianceMIBConformance 2 }

-- *****************************************************************
--
-- Compliance statement section
--
-- *****************************************************************

cohesityApplianceMIBCompliance MODULE-COMPLIANCE
  STATUS       current
  DESCRIPTION "The Cohesity Appliance Compliance Statement."
  MODULE    -- this module
    MANDATORY-GROUPS {
    caObjectGroup,
    caNotificationGroup
  }
  ::= { cohesityApplianceMIBCompliances 1 }

caObjectGroup OBJECT-GROUP
  OBJECTS {
    diskNotHealthyEvent,
    nodeIsDownEvent,
    diskOfflineEvent,
    upgradeFailedEvent,
    newDiskFoundEvent,
    logsDiskSpaceLowEvent,
    timeServiceEvent,
    missingDiskEvent,
    writeLimitEvent,
    memUncorrectableEccEvent,
    memCorrectableEccEvent,
    watchdogTriggeredEvent,
    tempOutOfHighRangeEvent,
    tempOutOfLowRangeEvent,
    voltOutOfHighRangeEvent,
    voltOutOfLowRangeEvent,
    hddDriveRemovedEvent,
    hddDrivePresentEvent,
    hddDriveFaultEvent,
    powerSupplyRemovedEvent,
    powerSupplyInsertedEvent,
    linkIsDownEvent,
    linkIsUpEvent,
    ipmiSelClearedEvent,
    nodeRebootedEvent,
    thermalTripTriggeredEvent,
    powerSupplyAcLostEvent,
    nodeChassisChangedEvent,
    raidDegradedEvent,
    diskOnlineEvent,
    systemLedAmberEvent,
    cpuThrottledEvent,
    clusterHealthEvent,
    diskMarkedOfflineEvent,
    activeDirectoryNotReachableEvent,
    kernelPanicEvent,
    clusterSpaceUsageHighEvent,
    viewBoxSpaceUsageHighEvent,
    nodeFailureIsNotToleratedEvent,
    searchClusterHealthEvent,
    backupJobFailedEvent,
    backupObjectFailedEvent,
    metadataServerUnreachableEvent,
    metadataUnavailableEvent,
    metadataShuffleNotProgressingEvent,
    cohesitySnmpTestEvent
  }
  STATUS       current
  DESCRIPTION "The Cohesity Appliance Object Group."
  ::= { cohesityApplianceMIBGroups 1 }

caNotificationGroup NOTIFICATION-GROUP
  NOTIFICATIONS {
    diskNotHealthyNotif,
    nodeIsDownNotif,
    diskOfflineNotif,
    upgradeFailedNotif,
    newDiskFoundNotif,
    logsDiskSpaceLowNotif,
    timeServiceNotif,
    missingDiskNotif,
    writeLimitNotif,
    memUncorrectableEccNotif,
    memCorrectableEccNotif,
    watchdogTriggeredNotif,
    tempOutOfHighRangeNotif,
    tempOutOfLowRangeNotif,
    voltOutOfHighRangeNotif,
    voltOutOfLowRangeNotif,
    hddDriveRemovedNotif,
    hddDrivePresentNotif,
    hddDriveFaultNotif,
    powerSupplyRemovedNotif,
    powerSupplyInsertedNotif,
    linkIsDownNotif,
    linkIsUpNotif,
    ipmiSelClearedNotif,
    nodeRebootedNotif,
    thermalTripTriggeredNotif,
    powerSupplyAcLostNotif,
    nodeChassisChangedNotif,
    raidDegradedNotif,
    diskOnlineNotif,
    systemLedAmberNotif,
    cpuThrottledNotif,
    clusterHealthNotif,
    diskMarkedOfflineNotif,
    activeDirectoryNotReachableNotif,
    kernelPanicNotif,
    clusterSpaceUsageHighNotif,
    viewBoxSpaceUsageHighNotif,
    nodeFailureIsNotToleratedNotif,
    searchClusterHealthNotif,
    backupJobFailedNotif,
    backupObjectFailedNotif,
    metadataServerUnreachableNotif,
    metadataUnavailableNotif,
    metadataShuffleNotProgressingNotif,
    cohesitySnmpTestNotif
  }
  STATUS       current
  DESCRIPTION "The Cohesity Appliance Notification Group."
  ::= { cohesityApplianceMIBGroups 2 }


END
